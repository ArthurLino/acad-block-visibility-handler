(defun c:CREATEVIS ()
    (if (setq objects (ssget))
        (repeat (setq i (sslength objects))
            (setq selected_object (ssname objects (setq i (1- i))))
            (command "_.BVSTATE" "N" (strcat "state " (rtos i 2 0)) "H")
            (command "_.BVSHOW" selected_object)
            (command "")
            (command "_C")
        )
    )  
)
